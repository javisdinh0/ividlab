(prompt "\n   MH  : Merge Hatch tool loaded. Command: MH")
(defun c:MH (/ ss entht sl i l dt dtht ent duoi dau tt)
  (defun getbdata (ent)
    (setq tt (entget ent)
	  tt (cdr (member (assoc 75 tt) (reverse tt)))
	  tt (cdr (member (assoc 91 tt) (reverse tt)))
    )
  )
  
  (command "_undo" "e" "_undo" "be")
  (prompt "\nSelect hatches to merge: ")
  (setq
    ss (ssget '((0 . "HATCH")))
    sl (if ss (sslength ss) 0)
    i  0
    l  0
  )
  (if (and ss (> sl 1))
    (progn
      (repeat sl
        (setq
          entht (ssname ss i)
          dtht  (getbdata entht)
          dt    (append dt dtht)
          l	    (+ l (cdr (assoc 91 (entget entht))))
          i	    (1+ i)
        )
      )
      (setq	ent  (ssname ss 0)
    	ss   (ssdel ent ss)
    	tt   (entget ent)
    	duoi (member (assoc 75 tt) tt)
    	dau  (reverse (member (assoc 91 tt) (reverse tt)))
    	tt   (append dau dt duoi)
    	tt   (subst (cons 91 l) (assoc 91 tt) tt)
      )
      (entmod tt)
      (command ".erase" ss "")
    )
    (prompt "\nPlease select more than one hatch to merge.")
  )
  (command "_undo" "e")
  (princ "\nAutoLISP tool collected and shared for non-profit by iViDLab.com")
  (princ)
)
